# ReceiverRequirements

## ReceiverConfigurableParameters: Requirements for the configurable receiver parameters. (Container)
The receiver should allow the user to modify the attenuation factor, delay, target SNR, carrier frequency, downsampling factor, and downsampling method used to receive the signal.
- Rationale: To allow the user to configure the receiver parameters when receiving the signal.

### UserConfigurableAttenuationFactor: The attenuation factor should be configurable by the user. (Functional)
The receiver should allow the user to modify the attenuation factor property.
- Rationale: To allow the user to configure the attenuation factor of the receiver.

### UserConfigurableDelay: The delay should be configurable by the user. (Functional)
The receiver should allow the user to modify the delay property.
- Rationale: To allow the user to configure the delay of the receiver.

### UserConfigurableTargetSNR: The target SNR should be configurable by the user. (Functional)
The receiver should allow the user to modify the target SNR property.
- Rationale: To allow the user to configure the target SNR of the receiver.

### UserConfigurableCarrierFrequency: The carrier frequency should be configurable by the user. (Functional)
The receiver should allow the user to modify the carrier frequency property.
- Rationale: To allow the user to configure the carrier frequency of the receiver.

### UserConfigurableDownsamplingFactor: The downsampling factor should be configurable by the user. (Functional)
The receiver should allow the user to modify the downsampling factor property.
- Rationale: To allow the user to configure the downsampling factor of the receiver.

### UserConfigurableDownsamplingMethod: The downsampling method should be configurable by the user. (Functional)
The receiver should allow the user to modify the downsampling method property.
- Rationale: To allow the user to configure the downsampling method of the receiver.

## ReceiverConstruction: Construction requirements for the receiver. (Functional)
The receiver class should allow the user to construct a receiver object by specifying name-value pairs for all configurable properties.
- Rationale: To provide a convenient and user-friendly API for constructing a receiver.

## Reception: The receiver should provide a means of reception. (Functional)
The receiver should provide a means for the user to enter a signal for reception. The input signal should be adjusted to simulate effects due to delay, attenuation, and noise, then demodulated, and returned in a timetable along with its corresponding time vector.
- Rationale: To provide a convenient and user-friendly API for the user to receiver their signal.
