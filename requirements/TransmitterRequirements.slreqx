# TransmitterRequirements

## TransmitterConfigurableParameters: Requirements for the configurable transmitter parameters. (Container)
The transmitter should allow the user to modify the carrier frequency, upsampling rate, and upsampling method used to transmit the signal.
- Rationale: To allow the user to configure the transmitter parameters when transmitting the signal.

### UserConfigurableCarrierFrequency: The carrier frequency should be configurable by the user. (Functional)
The transmitter should allow the user to modify the carrier frequency property.
- Rationale: To allow the user to configure the carrier frequency of the transmitter.

### UserConfigurableUpsamplingRate: The upsampling rate should be configurable by the user. (Functional)
The transmitter should allow the user to modify the upsampling rate property.
- Rationale: To allow the user to configure the upsampling rate of the transmitter.

### UserConfigurableUpsamplingMethod: The upsampling method should be configurable by the user. (Functional)
The transmitter should allow the user to modify the upsampling method property.
- Rationale: To allow the user to configure the upsampling method of the transmitter.

## TransmitterConstruction: Construction requirements for the transmitter. (Functional)
The transmitter class should allow the user to construct a transmitter object by specifying name-value pairs for all configurable properties.
- Rationale: To provide a convenient and user-friendly API for constructing a transmitter.

## Transmission: The transmitter should provide a means of transmission. (Functional)
The transmitter should provide a means for the user to enter a signal for transmission. The input signal should be modulated for transmission and returned in a timetable along with its corresponding time vector.
- Rationale: To provide a convenient and user-friendly API for the user to transmit their signal.
